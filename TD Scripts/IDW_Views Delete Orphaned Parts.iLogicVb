' Title: Views Delete Orphaned Parts
' Description: Deletes all ophaned part drawing views
' Version: 0.1

' Notes:
' - This rule searches all views to match them against the first parts list it finds in the document
' - If the Document In the View doesn't exist in the parts list reference assembly, it gets suppressed / deleted

' Define application / script name for prompts etc.
Dim strAppName As String = "IDW - Views - Delete Orphaned Parts"

' Check document is a drawing document
If ThisApplication.ActiveDocumentType <> DocumentTypeEnum.kDrawingDocumentObject Then
	MessageBox.Show("A drawing document must be open",strAppName)
	Exit Sub
End If

Dim oDoc As DrawingDocument = ThisApplication.ActiveDocument
Dim oSheet As Sheet = Nothing
Dim oPL As PartsList = Nothing
Dim oView As DrawingView = Nothing
Dim myList As New List(Of String)
Dim bPartListFound As Boolean = False

' Iterate through the sheets to find the first parts list
For Each oSheet In oDoc.Sheets
	' Check a parts list is on the sheet
	If oSheet.PartsLists.Count = 0 Then Continue For
	
	' Get first parts list if there is one or more
	oPL = oSheet.PartsLists.Item(1)
	
	' Set the found flag
	bPartListFound = True
	
	' Exit now it's found
	Exit For
Next

' Check if a parts list was found
If bPartListFound = False Then
	MessageBox.Show("No parts list found in this document",strAppName)
	Exit Sub
End If

' Get the first parts list on the first sheet, retrieve the assembly component reference
Dim oAsmDoc As AssemblyDocument = oPL.ReferencedDocumentDescriptor.ReferencedDocument

' Add all filenames to list, saves going through assembly each time
For Each oRefDoc As Document In oAsmDoc.AllReferencedDocuments
	myList.Add(oRefDoc.FullFileName)
Next

Dim strFilename As String = ""

' Start new transaction
'Dim oTx1 As Transaction = ThisApplication.TransactionManager.StartTransactionForDocumentOpen("Suppress Orphaned Views")

' Integer to keep track of view number
Dim iCount As Integer = 0

Try 
For Each oSheet In oDoc.Sheets
	
	' Check there are view on the sheet
	If oSheet.DrawingViews.Count = 0 Then Continue For

	For Each oView In oSheet.DrawingViews
		
		' Increase view number count
		iCount += 1
	
		' Update status bar
		ThisApplication.StatusBarText = "Processing view :" & iCount
		
		' Only run on part documents
		If oView.ReferencedDocumentDescriptor.ReferencedDocumentType <> DocumentTypeEnum.kPartDocumentObject Then Continue For
		
		' Only run on base views
		If oView.ViewType <> DrawingViewTypeEnum.kStandardDrawingViewType Then Continue For
			
		' Skip suppressed views
		If oView.Suppressed = True Then Continue For
		
		' Suppress view if it matches the list (replaces section below)
		oView.Suppressed = myList.Contains(oView.ReferencedDocumentDescriptor.ReferencedDocument.fullfilename)
		
		'' Delete view if it matches the list
		'If myList.Contains(oView.ReferencedDocumentDescriptor.ReferencedDocument.fullfilename) Then oView.Delete()
			
'		 ' Suppress based on boolean return of list check (string needs to match exactly, a partial match doesn't work for a list "contains")
'		If myList.Contains(oView.ReferencedDocumentDescriptor.ReferencedDocument.fullfilename) Then
'			' View found in assembly, do nothing or unsuppress, if unsupressing, you need to remove the skip suppressed views above
'			'oView.Suppressed = False
'		Else
'			' View not found in assembly, so hide
'			oView.Suppressed = True 
'		End If

		' End transaction
'		oTx1.End

	Next
Next

Catch Ex As Exception
	' Prompt user
	MessageBox.Show(Ex.Message, strAppName)
	
	' Error occurred so abort the transaction
'	oTx1.Abort
	
	' Exit now before trying to run the next section
	Exit Sub
End Try


' Prompt user to delete all suppressed views
Dim oResult As DialogResult = MessageBox.Show("Do you want to delete all of the suppressed views?", strAppName, MessageBoxButtons.YesNo)

' If no, exit the sub
If oResult = DialogResult.No Then Exit Sub
	
' Start new transaction
Dim oTx2 As Transaction = ThisApplication.TransactionManager.StartTransactionForDocumentOpen("Delete Orphaned Views")

' Iterate through all sheets
For Each oSheet In oDoc.Sheets
	' Iterate through all views in the sheet
	For Each oView In oSheet.DrawingViews
		' Delete all of the suppressed views
	    If oView.Suppressed = True Then oView.Delete()
	Next
Next

' End transaction
oTx2.End

' Notify user
MessageBox.Show("Complete",strAppName)
