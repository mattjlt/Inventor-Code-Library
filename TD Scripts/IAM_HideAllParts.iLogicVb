' Title: Hide All Parts
' Description: Hide all occurrences of selected parts in an assembly
' Version: 0.1

' Notes:
' - Replace all the prompts with a single windows form w/options
' - Add messagebox / prompt option to create a new view representation c/w a name field maybe? @ #####

Public Sub Main()

Dim oSelOcc As ComponentOccurrence
Dim strSelectPath As String = ""
Dim bFlag As Boolean = False
Dim bSelect As Boolean = False
Dim bAllLevels As Boolean = False

Select Case MsgBox("Do you want to hide assembly level occurrences (Yes) or all child occurrences (No)", MsgBoxStyle.YesNoCancel, "caption")
	Case MsgBoxResult.Yes
		bAllLevels = False
	Case MsgBoxResult.No
		bAllLevels = True
	Case MsgBoxResult.Cancel
		Exit Sub
End Select

Select Case MsgBox("Do you want to select an occurrence (Yes) or use standard file paths (No)", MsgBoxStyle.YesNoCancel, "caption")
	Case MsgBoxResult.Yes
		' Check if hiding on all levels or just the top level
		If bAllLevels = True Then
			oSelOcc = ThisApplication.CommandManager.Pick(SelectionFilterEnum.kAssemblyLeafOccurrenceFilter, "Select Occurrence To Hide")
		Else
			oSelOcc = ThisApplication.CommandManager.Pick(SelectionFilterEnum.kAssemblyOccurrenceFilter, "Select Occurrence To Hide")
		End If
		
		If oSelOcc Is Nothing Then : MessageBox.Show("No occurrence selected", "Component Selection") : Exit Sub : End If
		
		strSelectPath = oSelOcc.ReferencedDocumentDescriptor.FullDocumentName
		bSelect = True
		
	Case MsgBoxResult.Cancel
		Exit Sub
	Case MsgBoxResult.No
		bSelect = False
End Select

' ##################

Dim oDoc As AssemblyDocument = ThisApplication.ActiveDocument
Dim oCompDef As AssemblyComponentDefinition = oDoc.ComponentDefinition
Dim oOcc As ComponentOccurrence
'Dim oLeafOccs As ComponentOccurrencesEnumerator = Nothing
Dim oOccColl As Inventor.ObjectCollection = ThisApplication.TransientObjects.CreateObjectCollection()

' Check if hiding on all levels or just the top level
' The occurrences collection is throwing an error because its not an enumerator

If bAllLevels Then
	For Each oOcc In oCompDef.Occurrences.AllLeafOccurrences
		oOccColl.Add(oOcc)
	Next
Else
	For Each oOcc In oCompDef.Occurrences
		oOccColl.Add(oOcc)
	Next
End If



' Create a list of paths (used list object type as it's easier for people to read + understand than an array)
Dim lstFilePath As New List(Of String)
lstFilePath.Add("Washer")
lstFilePath.Add("Bolt")
lstFilePath.Add("Nut")
lstFilePath.Add("Screw")
lstFilePath.Add("Grease")
lstFilePath.Add("Pin")
lstFilePath.Add("AS 1968")
lstFilePath.Add("C:\Workspace\Work Orders\NCCC\Vendor library\Piping\Victaulic-Pipe\Vitaulic-Couplings")
lstFilePath.AddRange({ "M8", "M10", "M12", "M14", "M14", "M146", "M18", "M20", "M24", "M30" })
lstFilePath.Add("C:\Workspace\Libraries\Content Centre Files\")
lstFilePath.Add("C:\Workspace\Libraries\Standard Parts\Fasteners\")
lstFilePath.Add("C:\Workspace\Libraries\Standard Parts\Misc\Labels\Parts")
'lstFilePath.Add("NMC-")
lstFilePath.Add("C:\Workspace\Libraries\Standard Parts\OEM\Electrical\Electrical Parts")
lstFilePath.Add("C:\Workspace\Work Orders\NCCC\Vendor library\Hilti")


'lstFilePath.Add("C:\Workspace\Work Orders\QLD\NMQ-STANDARD PARTS\OEM\Weldlok")


Dim errorstep As String = "1"

' Progress Tracker
Dim iCount As Integer = 0

' Update status bar text to show current progress
ThisApplication.StatusBarText = "Processed " & iCount & " / " & oOccColl.Count

' Create a new transaction to enable single click undo for all items
Dim oTM As TransactionManager = ThisApplication.TransactionManager
Dim oTR As Transaction = oTM.StartTransaction(oDoc, "Hide All Parts")
	
	
Try
	
	' Iterate through all occurrences in collection and hide matching files
	For Each oOcc In oOccColl
		
		' Increase count
		iCount += 1 
		
		' Update status bar text to show current progress
		ThisApplication.StatusBarText = "Processed " & iCount & " / " & oOccColl.Count
		If oOcc.Definition.Type = ObjectTypeEnum.kWeldsComponentDefinitionObject Then Continue For
		If TypeOf oOcc.Definition Is VirtualComponentDefinition Then Continue For
		If oOcc.IsSubstituteOccurrence Then Continue For
		If oOcc.Suppressed Then Continue For
		
		errorstep = "Error Step: " & oOcc.Name
		strOcc = oOcc.ReferencedDocumentDescriptor.FullDocumentName
		errorstep = "2"

		' Test if selection option is used, run that if it is, otherwise skip to lstFilePath
		If bSelect = True Then
			' Use to lower to remove case sensitivity
			If strOcc.ToLower.Contains(strSelectPath.ToLower) Then
				oOcc.Visible = False
			End If
			Continue For
		End If
		
		' Iterate through each element in the list then hide occurrent if it matches
		For Each strElement As String In lstFilePath
			' Use to lower to remove case sensitivity
			If strOcc.ToLower.Contains(strElement.ToLower) Then
				' Check to see if it's already hidden - saves processing time
				If oOcc.Visible = True Then oOcc.Visible = False
				' Found a match so no need to compare the rest of the list
				Continue For
			End If
		Next

		errorstep = "6 - " & strOcc & oOcc.DefinitionDocumentType
	Next

Catch Ex As Exception
	MessageBox.Show(Ex.Message & " - " & errorstep)
	
Finally
	' Clear object collection (Not really necessary)
	oOccColl.Clear
	
	' Finish transaction
	oTR.End
End Try

	MessageBox.Show("Hide Parts Complete")

End Sub
