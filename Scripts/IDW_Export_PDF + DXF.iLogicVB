Imports system.Windows.Forms
' Title: Export Drawings To PDF + DXF
' Description: This exports drawings to PDF + DXF 
' Version: 0.2

' Notes:
' Export folders can be set below strFolderPDF & strFolderDXF

Sub Main()
	
	' Check active document is a drawing
	If ThisApplication.ActiveDocumentType <> Inventor.DocumentTypeEnum.kDrawingDocumentObject Then
		MessageBox.Show("A drawing document need to be active", "Document Print Error")  :	Exit Sub
	End If

	' Check document has been saved (can't get a filname from a document not saved)
	If ThisApplication.ActiveDocument.FullFileName = "" Then
		MessageBox.Show("Drawing need to be saved before printing", "Document Print Error") : Exit Sub
	End If

	' Confirm user wants to Print drawings
	If MessageBox.Show("This will export the active drawing" & ControlChars.NewLine & "Are you sure you want to continue?", "Confirmation", MessageBoxButtons.YesNo) <> DialogResult.Yes Then
		Exit Sub
	End If

	' Get active document
	Dim oDoc As DrawingDocument = ThisApplication.ActiveDocument

	' Check if there is a referenced model, update mass if there is (prevents an error on sheets with no model)
	If oDoc.ReferencedDocuments.Count > 1 Then
		' Read the mass to prevent N/A issue / triggers generation of mass (This will crash on a presentation file)
		Dim oMassStr As String = Round(ThisDrawing.ModelDocument.ComponentDefinition.MassProperties.Mass, 0)
		' Update to trigger the change in the drawing
		InventorVb.DocumentUpdate()
	End If

	' Get path + filename
	Dim strFilename As String = System.IO.Path.GetFileNameWithoutExtension(oDoc.FullFileName)

	' Get custom properties
	Dim strRev As String = iProperties.Value("Project", "Revision Number")

	' Check properties are valid
	If strRev = "" Then MessageBox.Show("Revision property is not set", "Document Print Error") : Exit Sub
	
	' Set output folder
	Dim strFolderPDF As String = System.IO.Path.GetDirectoryName(oDoc.FullFileName) & "\PDF"
	Dim strFolderDXF As String = System.IO.Path.GetDirectoryName(oDoc.FullFileName) & "\DXF"

	Dim strFilenamePDF As String = strFolderPDF & "\" & strFilename & " REV" & strRev & ".pdf"
	Dim strFilenameDXF As String = strFolderDXF & "\" & strFilename & " REV" & strRev & ".dxf"

	'Run export commands
	ExportPDF(oDoc,strFolderPDF,strFilenamePDF)
	ExportDXF(oDoc, strFolderDXF, strFilenameDXF)

	MessageBox.Show("Export Complete")
	ThisApplication.StatusBarText = "Export Complete"

End Sub

''' <summary>
''' Export Drawing to PDF
''' </summary>
''' <param name="oDoc">Target Document</param>
''' <param name="strfolder">Target Folder</param>
''' <param name="strFilename">Target Filename</param>
Sub ExportPDF(ByRef oDoc As DrawingDocument,ByVal strfolder As String,ByVal strFilename As String)
	
	' Update status bar for user
	ThisApplication.StatusBarText = "Exporting PDF"
	
	' Check PDF file exists, prompt user to continuet
	If System.IO.File.Exists(strFilename) Then
		If MessageBox.Show("PDF Exists, do you want to overwrite?", "Confirmation", MessageBoxButtons.YesNo) <> DialogResult.Yes Then
			' Cancel printing, file exists
			Exit Sub
		End If
	End If
	
	'Check for the PDF folder and create it if it does not exist
	If Not System.IO.Directory.Exists(strfolder) Then System.IO.Directory.CreateDirectory(strfolder)
		
	' Get the PDF translator Add-In.
	Dim PDFAddIn As TranslatorAddIn = ThisApplication.ApplicationAddIns.ItemById("{0AC6FD96-2F4D-42CE-8BE0-8AEA580399E4}")

	' Create translatin context
	Dim oContext As TranslationContext = ThisApplication.TransientObjects.CreateTranslationContext
	oContext.Type = kFileBrowseIOMechanism

	' Create a NameValueMap object
	Dim oOptions As NameValueMap = ThisApplication.TransientObjects.CreateNameValueMap

	' Create a DataMedium object
	Dim oDataMedium As DataMedium = ThisApplication.TransientObjects.CreateDataMedium

	' Check whether the translator has 'SaveCopyAs' options
	If PDFAddIn.HasSaveCopyAsOptions(oDoc, oContext, oOptions) Then
	    oOptions.Value("All_Color_AS_Black") = 1
	    oOptions.Value("Remove_Line_Weights") = 1
	    oOptions.Value("Vector_Resolution") = 400
	    oOptions.Value("Sheet_Range") = kPrintAllSheets
	    'oOptions.Value("Custom_Begin_Sheet") = 2 	' These arent used if you use kPrintAllSheets above
	    'oOptions.Value("Custom_End_Sheet") = 4 	' These arent used if you use kPrintAllSheets above
	End If

	'Set the destination file name
	oDataMedium.FileName = strFilename

	'Publish document.
	PDFAddIn.SaveCopyAs(oDoc, oContext, oOptions, oDataMedium)
End Sub

''' <summary>
''' Export drawing to DXF
''' </summary>
''' <param name="oDoc">Target document</param>
''' <param name="strfolder">Target folder</param>
''' <param name="strFilename">Target filename</param>
Sub ExportDXF(ByRef oDoc As DrawingDocument, ByVal strfolder As String, ByVal strFilename As String)

	' Update status bar for user
	ThisApplication.StatusBarText = "Exporting DXF"
	
	' Check DXF file exists, prompt user to continue
	If System.IO.File.Exists(strFilename) Then
		If MessageBox.Show("DXF Exists, do you want to overwrite?", "Confirmation", MessageBoxButtons.YesNo) <> DialogResult.Yes Then
			' Cancel printing, file exists
			Exit Sub
		End If
	End If

	'Check for the PDF folder and create it if it does not exist
	If Not System.IO.Directory.Exists(strfolder) Then System.IO.Directory.CreateDirectory(strfolder)
	
    ' Get the DXF translator Add-In.
    Dim DXFAddIn As TranslatorAddIn = ThisApplication.ApplicationAddIns.ItemById("{C24E3AC4-122E-11D5-8E91-0010B541CD80}")

	' Create translation context
    Dim oContext As TranslationContext = ThisApplication.TransientObjects.CreateTranslationContext
    oContext.Type = kFileBrowseIOMechanism

    ' Create a NameValueMap object
    Dim oOptions As NameValueMap = ThisApplication.TransientObjects.CreateNameValueMap

    ' Create a DataMedium object
    Dim oDataMedium As DataMedium = ThisApplication.TransientObjects.CreateDataMedium

	' Set INI file path
	Dim iniPath As String = System.IO.Path.Combine(My.Computer.FileSystem.SpecialDirectories.MyDocuments, "DXF_Export.ini") ' My documents folder
	'Dim iniPath As String = System.IO.Path.Combine(System.IO.Path.GetTempPath, "DXF_Export.ini") ' Temp folder
	
	' Check if INI exists, if not create it
	If Not System.IO.File.Exists(iniPath) Then
		' Create ini / exit if it fails
		If CreateINIFile(iniPath) = False Then Exit Sub
	End If

    ' Check whether the translator has 'SaveCopyAs' options
    If DXFAddIn.HasSaveCopyAsOptions(oDoc, oContext, oOptions) Then

        ' Create the name-value that specifies the ini file to use.
        oOptions.Value("Export_Acad_IniFile") = iniPath

    End If

    'Set the destination file name
    oDataMedium.FileName = strFilename

    'Publish document.
    DXFAddIn.SaveCopyAs(oDoc, oContext, oOptions, oDataMedium)
End Sub

''' <summary>
''' Create a new INI file with the relevant export settings defined
''' </summary>
''' <param name="strPath">Target path</param>
''' <returns>Boolean</returns>
Function CreateINIFile(ByVal strPath As String) As Boolean

    ' Save this to the temp folder
    'Path.Combine(Path.GetTempPath(),"filename.ini")
    'Dim filePath As String = System.IO.Path.Combine(My.Computer.FileSystem.SpecialDirectories.MyDocuments, "DXF_Export.ini")

    ' Scale / Space Configuration options
    '	                                SCALING	    SPACE
    'Base View Scale - Model Space    = Geometry	Model
    'Base View Scale - Layout         = Geometry	Layout
    'Sheet Scale - Model Space        = Text	    Model
    'Sheet Scale - Layout             = Text	    Layout
    'Full Scale(1:  1) - Model Space  = Full	    Model

    ' Create new string builder
    Dim oSB As New System.Text.StringBuilder

    ' Build INI file
    With oSB
        .AppendLine("[EXPORT SELECT OPTIONS]")
        .AppendLine("AUTOCAD VERSION=AutoCAD 2000") ' AutoCAD 2000 | AutoCAD 2004 | AutoCAD 2007 | AutoCAD 2010 | AutoCAD 2013 | AutoCAD 2018
        .AppendLine("CREATE AUTOCAD MECHANICAL=No")
        .AppendLine("USE TRANSMITTAL=No")
        .AppendLine("USE CUSTOMIZE=No")
        .AppendLine("CUSTOMIZE FILE=\Design Data\DWG-DXF\FlatPattern.xml") 'C:\Users\Public\Documents\Autodesk\Inventor 2019\Design Data\DWG-DXF\FlatPattern.xml" 
        .AppendLine("CREATE LAYER GROUP=No")
        .AppendLine("PARTS ONLY=No")

        .AppendLine("[EXPORT PROPERTIES]")
        .AppendLine("SELECTED PROPERTIES=")

        .AppendLine("[EXPORT DESTINATION]")
        .AppendLine("SPACE=Model") ' Model | Layout
        .AppendLine("SCALING=Geometry") ' Geometry | Text | Full
        .AppendLine("ALL SHEETS=Yes") ' Yes | No
        .AppendLine("MAPPING=MapsBest") ' LooksBest | MapsBest
        .AppendLine("MODEL GEOMETRY ONLY=No") ' Yes | No
        .AppendLine("EXPLODE DIMENSIONS=No") ' Yes | No
        .AppendLine("SYMBOLS ARE BLOCKED=Yes") ' Yes | No
        .AppendLine("AUTOCAD TEMPLATE=") ' None - If using, AutoCAD template filename example C:\CAD\templatename.dwt
        .AppendLine("DESTINATION DXF=Yes") 'Yes | No
        .AppendLine("USE ACI FOR ENTITIES AND LAYERS=No") 'Yes | No

        .AppendLine("[EXPORT LINE TYPE & LINE SCALE]")
        .AppendLine("LINE TYPE FILE=COMPATIBILITY\Support\invISO.lin") ' C:\Users\Public\Documents\Autodesk\Inventor 2019\COMPATIBILITY\Support\invISO.lin
        .AppendLine("Continuous=Continuous;0.")
        .AppendLine("Dashed=DASHED;0.")
        .AppendLine("Dashed Space=DASHED_SPACE;0.")
        .AppendLine("Long Dash Dotted=LONG_DASH_DOTTED;0.")
        .AppendLine("Long Dash Double Dot=LONG_DASH_DOUBLE_DOT;0.")
        .AppendLine("Long Dash Triple Dot=LONG_DASH_TRIPLE_DOT;0.")
        .AppendLine("Dotted=DOTTED;0.")
        .AppendLine("Chain=CHAIN;0.")
        .AppendLine("Double Dash Chain=DOUBLE_DASH_CHAIN;0.")
        .AppendLine("Dash Double Dot=DASH_DOUBLE_DOT;0.")
        .AppendLine("Dash Dot=DASH_DOT;0.")
        .AppendLine("Double Dash Dot=DOUBLE_DASH_DOT;0.")
        .AppendLine("Double Dash Double Dot=DOUBLE_DASH_DOUBLE_DOT;0.")
        .AppendLine("Dash Triple Dot=DASH_TRIPLE_DOT;0.")
        .AppendLine("Double Dash Triple Dot=DOUBLE_DASH_TRIPLE_DOT;0.")
    End With
MessageBox.Show(strPath)
	Try
		' Write file to path
    	IO.File.WriteAllText(strPath, oSB.ToString)
	Catch Ex As Exception
		MessageBox.Show("There was an error writing the ini file, check you have permission to edit the target directory")
		' Write failed
		Return False
	End Try
	
	' Write succeeded
	Return True

End Function
