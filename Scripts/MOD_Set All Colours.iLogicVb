Imports System.Windows.Forms
AddReference "System.Drawing.dll"
Imports System.Drawing
Imports Inventor
Imports clsSharedFunctions ' Globally import so it's available to all classes
' Title: Set All Colours
' Description: Change all parts to be the same colour
' Version: 0.2

' Notes:
' - Add option to remove part body + feature overrides - added but currently testing
' - The only errors encountered so far are when a derived part has errors (crashed features) and needs updating


Public Class RunMyForm
	
	Private Sub Main
	
		Dim strAppName As String = "Set Part Colours"
		
		' Check a document is open
		If ThisApplication.Documents.Count = 0 Then
			MessageBox.Show("No Documents Are Open",strAppName)
			Exit Sub
		End If
	
		' Get current document
		Dim oDoc As Inventor.Document = ThisApplication.ActiveEditDocument
		
		' Check document type
		If oDoc.DocumentType <> Inventor.DocumentTypeEnum.kPartDocumentObject And oDoc.DocumentType <> Inventor.DocumentTypeEnum.kAssemblyDocumentObject Then
			MessageBox.Show("An assembly or part document must be open",strAppName)				
			Exit Sub
		End If
		
		' Get list of active library appearances
		Dim appearanceList As New List(Of String)
		
		'ThisApplication.AssetLibraries.Item("Favourites")
		'ThisApplication.AssetLibraries.Item("Autodesk Appearance Library")
		
		' Iterate through all active render styles
		For Each oRS As RenderStyle In oDoc.RenderStyles
			' Add render style name to list
			appearanceList.Add(oRS.Name)
		Next
		
		' Create new instance of the custom form (sends appearance list to form)
        Dim myfrm As New CustomForm(appearanceList)
	ScaleForm(myfrm)
		
		Dim strAppearance As String = ""
		Dim bClearOverride As Boolean = True
		Dim bClearAppearanceOverride As Boolean = False
		
		' Display the custom form result
		If (myfrm.ShowDialog() = DialogResult.OK) Then
			' Use ShowDialog so it waits for user / form close before continuing
        	strAppearance = myfrm.myResult
			bClearOverride = myfrm.bOverride
			bClearAppearanceOverride = myfrm.bClearAppearanceOverride
		Else
			' Do nothing if dialog was cancelled
			Exit Sub
    	End If
			
		
		' Create new transaction
		Dim oTx As Transaction = ThisApplication.TransactionManager.StartTransaction(oDoc, strAppName)
		
		' Get active document directory
		Dim strParentDirectory As String = System.IO.Path.GetDirectoryName(oDoc.FullFileName)
		
		Dim iCount As Integer = oDoc.AllReferencedDocuments.Count
		Dim x As Integer = 0
		
		' Check active document type
		If oDoc.DocumentType = DocumentTypeEnum.kAssemblyDocumentObject Then
			' Iterate through all referenced documents
			For Each oRefDoc As Inventor.Document In oDoc.AllReferencedDocuments
				
				' Increase count + update status
				x += 1
				ThisApplication.StatusBarText = "Processing part " & x & " of " & iCount
				
				' Skip Master Files
				If oRefDoc.FullFileName.ToLower.Contains("master") Then Continue For
					
				' Check file is modifiable
				If Not oRefDoc.IsModifiable Then Continue For ' This check not really necessary

				' Only do files in same directory
				If oRefDoc.FullFileName.Contains(strParentDirectory) Then ChangeColour(oRefDoc,strAppearance,bClearOverride)
			Next
		ElseIf oDoc.DocumentType = DocumentTypeEnum.kPartDocumentObject Then
			ChangeColour(oDoc,strAppearance,bClearOverride)
		End If

		' End transaction
		oTx.End
		
		' Update Assembly Document
		oDoc.Update()
		
		' Update status
		ThisApplication.StatusBarText = "Processing complete"
		
	    End Sub
		
	Sub ChangeColour(ByVal oDoc As Inventor.Document,ByVal strAppearance As String,ByVal bClearOverride As Boolean)
	
		Try 
			' Check document is a part document
			If oDoc.DocumentType <> DocumentTypeEnum.kPartDocumentObject Then Exit Sub
				
			' Redefine as part document
			Dim oPartDoc As PartDocument = oDoc
	
			' Check if part is derived and if derived colour override is wanted
			If oPartDoc.ComponentDefinition.ReferenceComponents.DerivedPartComponents.Count > 0 And bClearOverride Then
				' Iterate through each derived component
				For Each oDComp As Inventor.DerivedPartComponent In oPartDoc.ComponentDefinition.ReferenceComponents.DerivedPartComponents
					' Get the definition
					Dim oDDef As Inventor.DerivedPartDefinition = oDComp.Definition
					' Change derived settings
					oDDef.UseColorOverridesFromSource = False
					' Push changes back to derived part
					oDComp.Definition = oDDef
				Next
				
			End If
			
			' Clear appearance overrides if selected
			If bClearOverride Then oPartDoc.ComponentDefinition.ClearAppearanceOverrides()
				
			' Create new instance of render style
			Dim oNewColor As RenderStyle = oPartDoc.RenderStyles.Item(strAppearance)
			
			' Change render style if it doesn't match
			If Not oPartDoc.ActiveRenderStyle Is oNewColor Then
			    oPartDoc.ActiveRenderStyle = oNewColor
			End If
			
		Catch Ex As Exception
			MessageBox.Show(Ex.Message & System.Environment.NewLine & "An unexpected error occurred" _
			& System.Environment.NewLine & oDoc.FullFileName, "Change Colour")
		End Try

	End Sub
End Class

Public Class CustomForm
	Inherits System.Windows.Forms.Form
	
	Public myResult As String = "Not Set"
	Public bOverride As Boolean = True
	Public bClearAppearanceOverride As Boolean = False ' Default to false as it's not always needed
	
	Public Sub New(ByRef appearanceList As List(Of String))
		
		' This is run when a new instance of the form is created		
		oForm = Me
		
		With oForm
			' Set up form	
			.FormBorderStyle = FormBorderStyle.FixedToolWindow 'Fixed3D / FixedDialog / FixedSingle / FixedToolWindow / None / Sizable / SizableToolWindow
			'.MaximizeBox = False
			'.MinimizeBox = False
			.StartPosition = FormStartPosition.CenterScreen
			.Width = 300
			.Height = 200
			.TopMost = True
			.Text = "Set Part Colours"
			.Name = "Set Part Colours"
			
		End With

		Dim Button1 As New Button()
		With Button1
			'.Font = myfnt
			.Text = "Start"
			.Width = 100
			.Height = 30
			'.Top = 60
			'.Left = oForm.Width/2 - 100/2
			.Enabled = True
			.Dock = DockStyle.Bottom
		End With

		' Create a selection box and load list
		Dim ComboBox1 As New ComboBox()
		With ComboBox1
			.Name = "cb_appearances"
			.Items.Clear()
			.Items.AddRange(appearanceList.ToArray)
			.SelectedIndex = 1
			.Top = 25
			.Left = 25
			.DropDownWidth = 300
			.Width = 225
			' Users can select from list / start typing to search
			'.DropDownStyle = Dropdownlist
			' This will prevent invalid typing / not matching selections
			.AutoCompleteMode = Append
		End With
		
		Dim CheckBox1 As New CheckBox()
		With CheckBox1
			.Name = "check_colour"
			.Text = "Remove derived colour override"
			.Width = 225
			.Top = 50
			.Left = 25
			.Checked = True
		End With
		
		Dim CheckBox2 As New CheckBox()
		With CheckBox2
			.Name = "check_override"
			.Text = "Remove appearance overrides"
			.Width = 225
			.Top = 75
			.Left = 25
			.Checked = False
		End With
		

		'Add your Event handler
		AddHandler Button1.Click, AddressOf Button1_Click  
		AddHandler ComboBox1.KeyPress, AddressOf ComboBox1_KeyPress
		AddHandler CheckBox1.CheckedChanged, AddressOf CheckBox1_CheckedChanged
		AddHandler CheckBox2.CheckedChanged, AddressOf CheckBox2_CheckedChanged
		
		'Add controls to form
		oForm.Controls.Add(Button1)
		oForm.Controls.Add(ComboBox1)
		oForm.Controls.Add(CheckBox1)
		oForm.Controls.Add(CheckBox2)
		
		' Set default dialog result
		Me.DialogResult = System.Windows.Forms.DialogResult.None
		
		
	End Sub

	Private Sub CustomForm_FormClosing(ByVal sender As Object, ByVal e As System.Windows.Forms.FormClosingEventArgs) Handles Me.FormClosing
	' Only run if dialog cance "x" button is clicked
	If Me.DialogResult = DialogResult.Cancel Then
	    If MessageBox.Show("Are you sure to close this application?", "Close", MessageBoxButtons.YesNo, MessageBoxIcon.Question) = System.Windows.Forms.DialogResult.Yes Then
		
	    Else
	      e.Cancel = True
	    End If
	End If
	 End Sub
  
	Private Sub Button1_Click(ByVal sender As System.Object, ByVal E As System.EventArgs)

		Dim oCB As ComboBox = Me.Controls.Item("cb_appearances")
		myResult = oCB.Text
		
		' Validate combo box text
		If oCB.Items.Contains(oCB.Text) = False Then
			MessageBox.Show("Selection is not in the list")
			Exit Sub
		End If
		'myResult = Me.Controls.Item("cb_appearances").Text
			
		Me.DialogResult = System.Windows.Forms.DialogResult.OK
		Me.Close		
	End Sub
	
	Private Sub CheckBox1_CheckedChanged(ByVal sender As System.Object, ByVal E As EventArgs)
		Dim check1 As CheckBox = Me.Controls.Item("check_colour")
		bOverride = check1.Checked
	End Sub
	
	Private Sub CheckBox2_CheckedChanged(ByVal sender As System.Object, ByVal E As EventArgs)
		Dim check1 As CheckBox = Me.Controls.Item("check_override")
		bClearAppearanceOverride = check1.Checked
	End Sub
	
	Private Sub ComboBox1_KeyPress(ByVal sender As Object, ByVal e As System.Windows.Forms.KeyPressEventArgs)
		' Limit key press entries via string matching the combo box list
        If e.KeyChar = ControlChars.Back AndAlso e.KeyChar = ControlChars.Back Then
            Return
        End If

        Dim t As String = sender.Text
        Dim typedT As String = t.Substring(0, sender.SelectionStart)
        Dim newT As String = typedT + e.KeyChar

        Dim i As Integer = sender.FindString(newT)
        If i = -1 Then
            e.Handled = True
        End If
End Sub



End Class

Public Class clsSharedFunctions
	
	Public Shared strAppName As String = "Set All Colours"	

	Public Shared Sub ScaleForm(WindowsForm As System.Windows.Forms.Form)
    Using g As System.Drawing.Graphics = WindowsForm.CreateGraphics
        Dim sngScaleFactor As Single = 1
        Dim sngFontFactor As Single = 1
        If g.DpiX > 96 Then
            sngScaleFactor = g.DpiX / 96
            'sngFontFactor = 96 / g.DpiY
        End If
        If WindowsForm.AutoScaleDimensions = WindowsForm.CurrentAutoScaleDimensions Then
            'ucWindowsFormHost.ScaleControl(WindowsForm, sngFontFactor)
            WindowsForm.Scale(sngScaleFactor)
        End If
    End Using
	End Sub
End Class
