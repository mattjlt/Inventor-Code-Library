' Title: View Label Copy
' Description: Copy one view label (formatted text) to another view
' Version: 0.1

' Notes:
' - Includes all formatted text

' Check a document is open
If ThisApplication.Documents.VisibleDocuments.Count = 0 Then
	MessageBox.Show("A Drawing Document needs to be open")
	Exit Sub
End If

' Check active document
If ThisApplication.ActiveDocumentType <> Inventor.DocumentTypeEnum.kDrawingDocumentObject Then
	MessageBox.Show("A Drawing Document needs to be open")
	Exit Sub
End If

' Initialise selection
Dim oVLsource As Inventor.DrawingViewLabel = ThisApplication.CommandManager.Pick(Inventor.SelectionFilterEnum.kDrawingViewLabelFilter, "Select view label to copy")

' Check selection was made
If oVLsource Is Nothing Then
	MessageBox.Show("Nothing was selected")
	Exit Sub
End If

' Create view label property and set to view label
Dim strLabel As String = oVLsource.FormattedText

LoopLabel :

' Initialise selection
Dim oVLtarget As Inventor.DrawingViewLabel = ThisApplication.CommandManager.Pick(Inventor.SelectionFilterEnum.kDrawingViewLabelFilter, "Select view label to change" & ControlChars.NewLine & " Hold Shift / Ctrl to multi place")

' Check selection was made
If oVLtarget Is Nothing Then
	MessageBox.Show("Nothing was selected")
	Exit Sub
End If

' Change label to source
oVLtarget.FormattedText = strLabel
	
Do While My.Computer.Keyboard.CtrlKeyDown Or My.Computer.Keyboard.ShiftKeyDown
	GoTo LoopLabel
Loop
