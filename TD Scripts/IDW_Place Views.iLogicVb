Imports System.Windows.Forms
AddReference "System.Drawing.dll"
Imports System.Drawing
Imports Inventor
Imports clsSharedFunctions ' Globally import so it's available to all classes
Imports System.Threading
' Title: Place Detail Items
' Description: Get all listed items from BOM for view placement
' Version: 0.0a

' Notes:


Public Class RunMyForm
	Private Sub Main
				
		' Check a document is open
		If ThisApplication.Documents.Count = 0 Then
			MessageBox.Show("No Documents Are Open",clsSharedFunctions.strAppName)
			Exit Sub
		End If
	
		' Check there is an active drawing document
		If ThisApplication.ActiveDocumentType <> Inventor.DocumentTypeEnum.kDrawingDocumentObject Then
			MessageBox.Show("A drawing document must be open",clsSharedFunctions.strAppName)
			Exit Sub
		End If
		
		' Get current document
		Dim oDoc As Inventor.DrawingDocument = ThisApplication.ActiveDocument
		
		' Create new instance of the custom form (sends partslist to form)
        Dim myfrm As New CustomForm(ThisApplication,oDoc)
		myfrm.Show()
		
	    End Sub
End Class

Public Class CustomForm
	Inherits System.Windows.Forms.Form
	
	Public myResult As String = "Not Set"
	
	' Class global inventor access
	Public Shared ThisApplication As Inventor.Application
	
	'Get list + inventor application access from parent class (Can't access inventor from a new class otherwise)
	Public Sub New(ByRef InvApp As Inventor.Application,ByRef oDoc As Inventor.DrawingDocument)
		
		' This is run when a new instance of the form is created		
		oForm = Me
		
		' Set global inventor application access from parent class
		ThisApplication = InvApp
		
		With oForm
			' Set up form	
			.FormBorderStyle = FormBorderStyle.SizableToolWindow 'Fixed3D / FixedDialog / FixedSingle / FixedToolWindow / None / Sizable / SizableToolWindow
			'.MaximizeBox = False
			'.MinimizeBox = False
			.StartPosition = FormStartPosition.CenterScreen
			.Width = 400
			.Height = 650
			.TopMost = True
			.Text = "Place Views"
			.Name = "Place Views"
		End With

		Dim Button1 As New Button()
		With Button1
			'.Font = myfnt
			.Text = "Place View"
			.Width = 100
			.Height = 30
			'.Top = 60
			'.Left = oForm.Width/2 - 100/2
			.Enabled = True
			.Dock = DockStyle.Bottom
		End With

		Dim oLV As New ListView
		With oLV
	        .View = System.Windows.Forms.View.Details
	        .FullRowSelect = True
			.Columns.Add("Detailed",75,System.Windows.Forms.HorizontalAlignment.Center)
	        .Columns.Add("Item",50,System.Windows.Forms.HorizontalAlignment.Center)
	        .Columns.Add("Description",250,System.Windows.Forms.HorizontalAlignment.Left)
	        .Columns.Add("Filename", 200, System.Windows.Forms.HorizontalAlignment.Left)
			.Columns.Add("FullFilename",200,System.Windows.Forms.HorizontalAlignment.Left)
			
			.Dock = DockStyle.Fill
			' Name listview for button control direct access
			.Name = "ListView_Partslist"
		End With

			
		'Add your Event handler
		AddHandler Button1.Click, AddressOf Button1_Click
		AddHandler oLV.DoubleClick,AddressOf Button1_Click
		
		'Add controls to form
		oForm.Controls.Add(Button1)
		oForm.Controls.Add(oLV)
		oLV.BringToFront

		' Get Parts List
		Dim lstBOM As New List(Of clsBOMRow)
		lstBOM = clsSharedFunctions.LoadPartsList(oDoc) 

		' Load BOM list into ListView
		For Each oRefBOMRow As clsBOMRow In clsSharedFunctions.LoadPartsList(oDoc)
			oLV.Items.Add(New ListViewItem({If(oRefBOMRow._Detailed,"True","False"),oRefBOMRow._Item,oRefBOMRow._Description,oRefBOMRow._Filename,oRefBOMRow._FullFilename}))
		Next
		
		' Set default dialog result
		Me.DialogResult = System.Windows.Forms.DialogResult.None
	
	End Sub

	Private Sub CustomForm_FormClosing(ByVal sender As Object, ByVal e As System.Windows.Forms.FormClosingEventArgs) Handles Me.FormClosing
	' Only run if dialog cance "x" button is clicked
	If Me.DialogResult = DialogResult.Cancel Then
	    If MessageBox.Show("Are you sure to close this application?", "Close", MessageBoxButtons.YesNo, MessageBoxIcon.Question) = System.Windows.Forms.DialogResult.Yes Then
		
	    Else
	      e.Cancel = True
	    End If
	End If
	 End Sub
  
	Private Sub Button1_Click(ByVal sender As System.Object, ByVal E As System.EventArgs)
		
		' Access form list view
		Dim tempLV As ListView = TryCast(Me.Controls("ListView_Partslist"), ListView)
		
		' Check selection was made, if not, exit out
		If tempLV.SelectedItems.Count = 0 Then
			MessageBox.Show("An item needs to be selected", "Selection Error")
			Exit Sub
		End If

		' Get selected item text
		Dim strFilename As String = tempLV.SelectedItems.Item(0).SubItems(4).Text
		
		' Verify filename is valid
		If Not System.IO.File.Exists(strFilename) Then
			' Filename is invalid
			MessageBox.Show("Filename :" & strFilename & ControlChars.NewLine & "Does Not Exist", "Selection Error")
			Exit Sub
		End If
		
		' Post filename to internal clipboard to be read by place view command
		ThisApplication.CommandManager.PostPrivateEvent(PrivateEventTypeEnum.kFileNameEvent, strFilename)
			
		' Initiate view place command - Execute2(False) allows user to manually place view
		ThisApplication.CommandManager.ControlDefinitions.Item("DrawingBaseViewCmd").Execute2(False)
		
		
		' Change sub item to detailed, should just close / open form and reload for better user interface but
		' due to inventor problems where it doesn't wait for user selection to finish, need to do it like this for now.
		tempLV.SelectedItems.Item(0).SubItems(0).Text = "True"
				
	End Sub
	
End Class

Public Class clsSharedFunctions
	
	Public Shared strAppName As String = "Quick View Place"
	
	Public Shared Function GetAllViewFilenames(ByRef oDoc As DrawingDocument) As List(Of String)

		' Need to create a new list to return as result, can't directly return function like a normal string
		Dim tempList As New List(Of String)
		
		' Iterate through all sheets
		For Each oSheet As Inventor.Sheet In oDoc.Sheets
			' Iterate through all base views
			For Each oView As Inventor.DrawingView In oSheet.DrawingViews
				' Check view type is base type
				If oView.ViewType = Inventor.DrawingViewTypeEnum.kStandardDrawingViewType Then
					' Add view filename to list
					tempList.Add(oView.ReferencedDocumentDescriptor.FullDocumentName)
				End If
			Next
		Next
		
		Return tempList
	End Function
	
	Public Shared Function LoadPartsList(ByRef oDoc As DrawingDocument) As List(Of clsBOMRow)
		
		' Define partslist placeholder
		Dim oPL As Inventor.PartsList = Nothing
		
		' Create parts list found flag
		Dim bPartsListFound As Boolean = False

		' Get first part list
		For Each oSheet As Inventor.Sheet In oDoc.Sheets
			' Check there is a parts list

			If oSheet.PartsLists.Count = 0 Then Continue For
				' There is a parts list if up to here
				' Get parts list and exit iteration

				oPL = oSheet.PartsLists(1)

				bPartsListFound = True
			Exit For
		Next

		' Check a parts list was found
		If bPartsListFound = False Then
			MessageBox.Show("No Parts List Found", strAppName)
			Exit Function
		End If

		' Get all view filenames
		Dim lstViews As New List(Of String)
		lstViews = GetAllViewFilenames(oDoc)

		' Convert Parts List Into Array
		Dim lstBOM As New List(Of clsBOMRow)

		' Iterate through each parts list row
		For Each oRow As Inventor.PartsListRow In oPL.PartsListRows
			' Get referenced document filename
			Dim strFilename As String = oRow.ReferencedRows.Item(1).BOMRow.ComponentDefinitions.Item(1).Document.Fullfilename
			' Create new BOM Row Class Instance
			Dim newRow As New clsBOMRow()
			With newRow
				._Detailed = lstViews.Contains(strFilename) ' Check if filename is present in list of base views
				._Item = oRow.Item(1).Value.ToString ' Item Column
				._Description = oRow.Item(3).Value.ToString ' Description
				._Filename = System.IO.Path.GetFileName(strFilename)
				._FullFilename = strFilename
			End With
			' Add newRow into BOM List
			lstBOM.Add(newRow)
		Next

		Return lstBOM
	End Function
		
	Public Shared Sub wait(ByVal seconds As Integer)
    	For i As Integer = 0 To seconds * 100
	        System.Threading.Thread.Sleep(10)
	        System.Windows.Forms.Application.DoEvents()
    	Next
	End Sub

End Class

Public Class clsBOMRow
	Public Property _Detailed As Boolean
    Public Property _Item As String
    Public Property _Description As String
    Public Property _Filename As String
	Public Property _FullFilename As String

	Public Sub New
			' This allows the creation of the class without having to prefill all the fields
	End Sub

    Public Sub New(ByVal bDetailed As Boolean,
					ByVal strItem As String,
					ByVal strDescription As String,
					ByVal strFilename As String,
					ByVal strFullFilename As Boolean)
		_Detailed = bDetailed
        _Item = strItem
        _Description = strDescription
        _Filename = strFilename
		_Filename = strFullFilename
        
	End Sub
	
End Class
