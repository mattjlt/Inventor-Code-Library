' Check a document is open
If ThisApplication.Documents.VisibleDocuments.Count = 0 Then
	MessageBox.Show("A Drawing Document needs to be open")
	Exit Sub
End If

' Check active document
If ThisApplication.ActiveDocumentType <> Inventor.DocumentTypeEnum.kDrawingDocumentObject Then
	MessageBox.Show("A Drawing Document needs to be open")
	Exit Sub
End If

' Get the active document
Dim oDoc As Inventor.DrawingDocument = ThisApplication.ActiveDocument

' Iterate through all sheets
For Each oSheet As Inventor.Sheet In oDoc.Sheets
	
	' Check there are views on the sheet
	If oSheet.DrawingViews.Count = 0 Then Continue For
		
	' Iterate through all views
	For Each oView As Inventor.DrawingView In oSheet.DrawingViews
		
		' Check view is a base view, skip if not
		If oView.ViewType <> Inventor.DrawingViewTypeEnum.kStandardDrawingViewType Then Continue For
			
		' Turn on view label if it isn't already
		oView.ShowLabel = True
		
		' Set formatted text (this is how you need to add all of your property fields etc.
		oView.Label.FormattedText = "<StyleOverride Underline='True'><Property Document='model' PropertySet='Design Tracking Properties' Property='Part Number' FormatID='{32853F0F-3444-11D1-9E93-0060B03C1CA6}' PropertyID='5'>PART NUMBER</Property></StyleOverride><Br/><Property Document='model' PropertySet='Design Tracking Properties' Property='Description' FormatID='{32853F0F-3444-11D1-9E93-0060B03C1CA6}' PropertyID='29'>DESCRIPTION</Property><Br/><Property Document='model' PropertySet='Inventor Summary Information' Property='Keywords' FormatID='{F29F85E0-4FF9-1068-AB91-08002B27B3D9}' PropertyID='5'>KEYWORDS</Property><Br/><StyleOverride FontSize='0.25'>(</StyleOverride><StyleOverride FontSize='0.25'><DrawingViewScale/></StyleOverride><StyleOverride FontSize='0.25'>)</StyleOverride>"
		
	Next ' Next view
Next ' Next sheet
