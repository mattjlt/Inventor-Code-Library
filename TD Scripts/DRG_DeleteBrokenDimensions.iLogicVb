' Check active document is a drawing document
If ThisApplication.ActiveDocumentType <> Inventor.DocumentTypeEnum.kDrawingDocumentObject Then
	MessageBox.Show("A drawing document must be open", "Broken Dimension Delete")
	Exit Sub
End If

' Get drawing document
Dim oDoc As DrawingDocument = ThisApplication.ActiveDocument

' Iterate through all sheets in document
For Each oSheet As Inventor.Sheet In oDoc.Sheets
	' Iterate through all dimensions in sheet
	For Each oDim As Inventor.DrawingDimension In oSheet.DrawingDimensions
		If oDim.Type = Inventor.ObjectTypeEnum.kOrdinateDimensionObject Then
			
			' Set dimension to ordinate dimension (not necessary but helps intellisense when coding)
			Dim oOrdDim As Inventor.OrdinateDimension = oDim
			
			' Check dimension is a member of an ordinate dimension set and if it's attached
			If oOrdDim.IsOrdinateSetMember And  oDim.Attached = False
				' Delete Dimension
				oDim.Delete
			End If
			
		End If
	Next
Next
