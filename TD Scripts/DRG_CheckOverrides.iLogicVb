Imports System.Windows.Forms
AddReference "System.Drawing.dll"
Imports System.Drawing
Imports Inventor
Imports clsSharedFunctions ' Globally import so it's available to all classes
Imports System.Threading

' Title: Place Detail Items
' Description: Get all listed items from BOM for view placement
' Version: 0.0a

' Notes:


Public Class RunMyForm
	Private Sub Main
				
		' Check a document is open
		If ThisApplication.Documents.Count = 0 Then
			MessageBox.Show("No Documents Are Open",clsSharedFunctions.strAppName)
			Exit Sub
		End If
	
		' Check there is an active drawing document
		If ThisApplication.ActiveDocumentType <> Inventor.DocumentTypeEnum.kDrawingDocumentObject Then
			MessageBox.Show("A drawing document must be open",clsSharedFunctions.strAppName)
			Exit Sub
		End If
		
		' Get current document
		Dim oDoc As Inventor.DrawingDocument = ThisApplication.ActiveDocument
		
		' Create new instance of the custom form (sends partslist to form)
        Dim myfrm As New CustomForm(ThisApplication,oDoc)
		myfrm.Show()
		
	    End Sub
End Class

Public Class CustomForm
	Inherits System.Windows.Forms.Form
	
	Public myResult As String = "Not Set"
	
	' Class global inventor access
	Public Shared ThisApplication As Inventor.Application
	
	'Get list + inventor application access from parent class (Can't access inventor from a new class otherwise)
	Public Sub New(ByRef InvApp As Inventor.Application,ByRef oDoc As Inventor.DrawingDocument)
		
		' This is run when a new instance of the form is created		
		oForm = Me
		
		' Set global inventor application access from parent class
		ThisApplication = InvApp
			
		
		With oForm
			' Set up form	
			.FormBorderStyle = FormBorderStyle.SizableToolWindow 'Fixed3D / FixedDialog / FixedSingle / FixedToolWindow / None / Sizable / SizableToolWindow
			'.MaximizeBox = False
			'.MinimizeBox = False
			.StartPosition = FormStartPosition.CenterScreen
			.Width = 500
			.Height = 300
			.TopMost = True
			.Text = "Compliance Check"
			.Name = "Compliance Check"

		End With

		Dim Button1 As New Button()
		With Button1
			'.Font = myfnt
			.Text = "Start"
			.Width = 100
			.Height = 40
			'.Top = 60
			'.Left = oForm.Width/2 - 100/2
			.Enabled = True
			.Dock = DockStyle.Bottom
		End With

		Dim oRTB As New RichTextBox()
		With oRTB
			.Dock = DockStyle.Fill
			' Name listview for button control direct access
			.Name = "textbox_log"
		End With

			
		'Add your Event handler
		AddHandler Button1.Click, AddressOf Button1_Click
		
		'Add controls to form
		oForm.Controls.Add(Button1)
		oForm.Controls.Add(oRTB)
		oRTB.BringToFront

		' Set default dialog result
		Me.DialogResult = System.Windows.Forms.DialogResult.None
		
		oRTB.AppendText("Drawing compliance check form, press start to begin")
		ScaleForm(oForm)

	End Sub

	Private Sub CustomForm_FormClosing(ByVal sender As Object, ByVal e As System.Windows.Forms.FormClosingEventArgs) Handles Me.FormClosing
	' Only run if dialog cance "x" button is clicked
	If Me.DialogResult = DialogResult.Cancel Then
	    If MessageBox.Show("Are you sure to close this application?", "Close", MessageBoxButtons.YesNo, MessageBoxIcon.Question) = System.Windows.Forms.DialogResult.Yes Then
		
	    Else
	      e.Cancel = True
	    End If
	End If
	 End Sub
  
	Private Sub Button1_Click(ByVal sender As System.Object, ByVal E As System.EventArgs)
		
		' Access form list view
		Dim oRTB As RichTextBox = TryCast(Me.Controls("textbox_log"), RichTextBox)
		Dim oDoc As Inventor.DrawingDocument = ThisApplication.ActiveDocument
		Dim oDim As Inventor.DrawingDimension
		
		' Set found flags
		Dim bDimsFound As Boolean = False
		Dim bBalloonFound As Boolean = False
		Dim iCount As Integer = 0 ' sheet count
		
		oRTB.Clear
		oRTB.AppendText("Drawing compliance check form, press start to begin")
		oRTB.AppendText(ControlChars.NewLine)
		
		For Each oSheet As Inventor.Sheet In oDoc.Sheets
			iCount = iCount + 1 'Increase sheet count
			
			oRTB.AppendText(ControlChars.NewLine)
			oRTB.AppendText("Checking Sheet: " & iCount & ControlChars.NewLine)
			
			' Iterate through all dimensions in sheet
			For Each oDim In oSheet.DrawingDimensions
				' Check if dimension value is overwritten
				If oDim.ModelValueOverridden Then
					bDimsFound = True
					oRTB.AppendText("Dimension override found: " & oDim.Text.Text & ControlChars.NewLine)
				End If
				If oDim.HideValue Then
					bDimsFound = True
					oRTB.AppendText("Dimension hidden value found: " & oDim.Text.Text & ControlChars.NewLine)
				End If
			Next
			
			' Iterate through all balloons in sheet
			For Each oBall As Inventor.Balloon In oSheet.Balloons
				' Iterate through all value sets in a balloon
				For Each oBV As Inventor.BalloonValueSet In oBall.BalloonValueSets
					' Need to check override value is not empty as when it's not used, it is empty
					If oBV.OverrideValue <> "" And oBV.OverrideValue <> oBV.ItemNumber Then
						bBalloonFound = True
						oRTB.AppendText("Balloon override found: Item " & oBV.Value & ControlChars.NewLine)
					End If
				Next	
			Next
		Next
		
		oRTB.AppendText(ControlChars.NewLine)
		oRTB.AppendText(ControlChars.NewLine)
		
		If bDimsFound = False Then oRTB.AppendText("No dimension overrides found" & ControlChars.NewLine)
		If bBalloonFound = False Then oRTB.AppendText("No balloon overrides found" & ControlChars.NewLine)
			
		
				
	End Sub
	
End Class

Public Class clsSharedFunctions
	
	Public Shared strAppName As String = "Drawing Compliance Form"	

	Public Shared Sub ScaleForm(WindowsForm As System.Windows.Forms.Form)
    Using g As System.Drawing.Graphics = WindowsForm.CreateGraphics
        Dim sngScaleFactor As Single = 1
        Dim sngFontFactor As Single = 1
        If g.DpiX > 96 Then
            sngScaleFactor = g.DpiX / 96
            'sngFontFactor = 96 / g.DpiY
        End If
        If WindowsForm.AutoScaleDimensions = WindowsForm.CurrentAutoScaleDimensions Then
            'ucWindowsFormHost.ScaleControl(WindowsForm, sngFontFactor)
            WindowsForm.Scale(sngScaleFactor)
        End If
    End Using
End Sub

End Class
