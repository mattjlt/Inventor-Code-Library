Imports System.Windows.Forms
AddReference "System.Drawing.dll"
' Title: Delete All Sketch Constraints
' Description: Deletes all constraints in the active sketch
' Version: 0.1

' Notes:
' - N/A

Sub Main
	
	Dim myForm As New CustomFormProgress(100,5,"No Caption")
	myForm.Show()
	
'	For i = myForm.oPB.Minimum To oPB.Maximum Step 5
'		'Sleep
'		Threading.Thread.Sleep(100) ' 100 milliseconds = 0.1 seconds
'		oPB.Value = i
'		oLbl.Text = "Status: " & oPB.Value & " of " & oPB.Maximum & " Complete"
'		myfrm.Update  ' This forces form to refresh label
'	Next
	
	MessageBox.Show("TaskComplete")
	
	Dim strAppName As String = "Delete Sketch Constraint"
	' Check the active edit object is a sketch
	If Not TypeOf ThisApplication.ActiveEditObject Is Sketch Then
        MessageBox.Show("A Sketch must be active for this to work",strAppName,MessageBoxButtons.OK)
        Exit Sub
    End If
		
	' Create dialog result object
	Dim oResult As DialogResult
	oResult = MessageBox.Show("Running this on large sketches can take a long time, do you want to continue?","Delete All Sketch Constraints",MessageBoxButtons.YesNoCancel)

	' Check what messagebox result was
	Select Case oResult
		Case DialogResult.Yes
			MessageBox.Show("Yes")
		Case Else
			Exit Sub
	End Select

	Try
		
	Select Case ThisApplication.ActiveEditObject.Type
		Case ObjectTypeEnum.kSketchBlockDefinitionObject
			' Do Nothing
		Case ObjectTypeEnum.kPlanarSketchObject
			' Do Nothing
		Case Else
			MessageBox.Show("A sketch needs to be active","Delete All Sketch Constraints")
			Exit Sub
	End Select

	Dim oGC As GeometricConstraint
	For Each oGC In ThisApplication.ActiveEditObject.GeometricConstraints
		If oGC.Deletable = True Then oGC.Delete
	Next


	Catch Ex As Exception
		' Do nothing
		MessageBox.Show(Ex.Message)
	Finally
		MessageBox.Show("Complete", "Delete All Sketch Constraints")
	End Try
End Sub

Public Sub MainForm

	Dim myfrm As New Form
	Dim oPB As New System.Windows.Forms.ProgressBar
	' add progress bar label e.g. xx of xx complete
	With oPB
		'.Anchor = anchorStyles.Top
		.Top = 70
		.Left = 40
		.Width = 200
		.Minimum = 0
		.Maximum = 100
		.Value = 0
	End With
	
	Dim oLbl As New Label
	With oLbl
		.Top = 25
		.Left = 40
		.AutoSize = False
		.Width = 200
		.BackColor = Transparent
		'.TextAlign = ContentAlignment.MiddleCenter
		.Text = "My PlaceHolder Text Here"
	End With
	
	With myfrm
		.FormBorderStyle = FormBorderStyle.FixedToolWindow 'Fixed3D / FixedDialog / FixedSingle / FixedToolWindow / None / Sizable / SizableToolWindow
		'.MaximizeBox = False
		'.MinimizeBox = False
		.StartPosition = FormStartPosition.CenterScreen
		
		.Width = 300
		.Height = 150
		.Text = "Progress Indicator"
		.TopMost = True
		.Controls.Add(oPB)
		.Controls.Add(oLbl)
		'.Update ' This forces form to refresh (fixes labels not correctly displaying / displaying as white)
	End With

	
	For i = oPB.Minimum To oPB.Maximum Step 5
		'Sleep
		Threading.Thread.Sleep(100) ' 100 milliseconds = 0.1 seconds
		oPB.Value = i
		oLbl.Text = "Status: " & oPB.Value & " of " & oPB.Maximum & " Complete"
		myfrm.Update  ' This forces form to refresh label
	Next
	
	MessageBox.Show("TaskComplete")
	myfrm.Close
	
	Exit Sub
	
	
	
End Sub

Public Class CustomFormProgress
	Inherits System.Windows.Forms.Form
	
	Public myResult As String = "TestResultHere"
	Public myProp1 As String = "TestProperty"
	
	Public Sub New(ByVal intMax As Integer, ByVal intStep As Integer,ByVal strCaption As String)
		' This is run when a new instance of the form is created
		
		oForm = Me
		
		With oForm
			' Set up form	
			.FormBorderStyle = FormBorderStyle.FixedToolWindow 'Fixed3D / FixedDialog / FixedSingle / FixedToolWindow / None / Sizable / SizableToolWindow
			.MaximizeBox = False
			.MinimizeBox = False
			.StartPosition = FormStartPosition.CenterScreen
			.Width = 300
			.Height = 150
			.TopMost = True
			.Text = "Progress Bar"
			.Name = "Progress Bar"			
		End With
		
		' add progress bar label e.g. xx of xx complete
		Dim oPB As System.Windows.Forms.ProgressBar
		With oPB
			.Name = "ProgressBar1"
			'.Anchor = anchorStyles.Top
			.Top = 70
			.Left = 40
			.Width = 200
			.Minimum = 0
			.Maximum = intMax
			.Value = 0
		End With
		
		Dim oLbl As New Label
		With oLbl
			.Name = "Label1"
			.Top = 25
			.Left = 40
			.AutoSize = False
			.Width = 200
			.BackColor = Transparent
			'.TextAlign = ContentAlignment.MiddleCenter
			.Text = "My PlaceHolder Text Here"
		End With

		' Add controls to form
		oForm.Controls.Add(oPB)
		oForm.Controls.Add(oLbl)
				
		'.Show
		'.Update ' This forces form to refresh (fixes labels not correctly displaying / displaying as white)
			
	End Sub
	
	Public Sub ProgressStep()
'		Dim oPB As System.Windows.Forms.ProgressBar = CType(Me.Controls("ProgressBar1"), System.Windows.Forms.ProgressBar)
'		oPB.PerformStep()
		
'		Dim oLbl As Label = CType(Me.Controls("Label1"), Label)
'        oLbl.Text = ((oPB.Value / oPB.Maximum) * 100).ToString & "% complete"
		
'        Me.Refresh()
'        'Application.DoEvents()
'        If oPB.Value = oPB.Maximum Then Me.Close()
    End Sub
	
'	Private Sub CustomForm_FormClosing(ByVal sender As Object, ByVal e As System.Windows.Forms.FormClosingEventArgs) Handles Me.FormClosing
'	    If MessageBox.Show("Are you sure to close this application?", "Close", MessageBoxButtons.YesNo, MessageBoxIcon.Question) = System.Windows.Forms.DialogResult.Yes Then
		
'	    Else
'	      e.Cancel = True
'	    End If
'	 End Sub


End Class
