' Title: Get View Sheet Positions
' Description: Search through all sheets in drawing document for part document views
' 	Get the Sheet number they are on and add it to a custom property inside the part.
' Version: 0.1a

' Notes:
' In progress....

Sub Main()

Dim oDoc As DrawingDocument = ThisApplication.ActiveDocument
Dim oRefDoc As Document
Dim strSheetNo As String
Dim errStep As String = "Step 0"

Try
' Iterate through all sheets
For Each oSheet As Sheet In oDoc.Sheets
	errStep =  "Step 1"
    ' Get sheet index number
    strSheetNo = Right(oSheet.Name, 1)
    errStep =  "Step 2"
    ' Iterate through all views in each sheet
    For Each oView As DrawingView In oSheet.DrawingViews
	
	' Skip all views not standard views
	If oView.ViewType <> Inventor.DrawingViewTypeEnum.kStandardDrawingViewType Then Continue For
	
	' Not sure if this checks if it is a base view aswell
	
        ' Check document is a part
		errStep =  "Step 3"
        If oView.ReferencedDocumentDescriptor.ReferencedDocumentType = kPartDocumentObject Then
			errStep =  "Step 4"
            ' Get referenced document
            oRefDoc = oView.ReferencedDocumentDescriptor.ReferencedDocument
            errStep =  "Step 5 - " & oView.Name
			
            ' Check if view is a flat pattern or normal view
            ' Probably need a check on this to see if the view has been detailed elsewhere as a flat pattern + normal view
            'If oView.IsFlatPatternView Then
            '    oRefDoc.PropertySets("Inventor User Defined Properties").Item("Remarks").Value = "PRESSED,DETAIL REF SHT " & strSheetNo
            'Else
				Modify_iProperty(oRefDoc,"Inventor User Defined Properties","Remarks","REF SHT " & strSheetNo)
			'End If
			errStep =  "Step 6"
        End If
    Next
Next

Catch Ex As Exception
	MessageBox.Show (Ex.Message & System.Environment.NewLine & errStep ,"Error - Get View Sheet Positions")
End Try

' Update to reflect changes
InventorVb.DocumentUpdate()

End Sub

Sub Modify_iProperty(ByRef oDoc As Document, ByVal strPropset As String, ByVal strProp As String, ByVal strValue As String)

	' This sub checks if an iproperty exists before creating / modifying it.
	' If this check isn't done it can throw an error if you try modify a non-existant property
	
	'define property collection
	Dim oPropSet As PropertySet = oDoc.PropertySets(strPropset)

	Try
				'set custom property value
				oPropSet.Item(strProp).Value = strValue
	Catch
				' Assume error means not found so create it
				oPropSet.Add(strValue, strProp)
	End Try
	
End Sub
