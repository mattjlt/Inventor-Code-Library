' Title: Delete All Empty Parts
' Description: Deletes all empty part files in an assembly document
' Version: 0.1

' Notes:
' - Maybe have all these get added to a list
' - Could make this a standard snippet where all occurrences are added to a list to be actioned with an interactive list form

' Define app name for all prompts
Dim strAppName As String = "Delete All Empty Parts"

If ThisApplication.ActiveDocumentType <> DocumentTypeEnum.kAssemblyDocumentObject Then
	MessageBox.Show("An assembly document needs to be open",strAppName)
End If

Dim oDoc As AssemblyDocument = ThisApplication.ActiveDocument

Dim occList As New List(Of String)

For Each oOcc As ComponentOccurrence In oDoc.ComponentDefinition.Occurrences
	' Skip assembly occurrences
	If oOcc.DefinitionDocumentType = DocumentTypeEnum.kAssemblyDocumentObject Then Continue For
		
	' Need to add skips in for weld occurrences + reference parts too / virtual parts
	If oOcc.IsPatternElement Then Continue For
	If oOcc.Definition.Type = ObjectTypeEnum.kWeldsComponentDefinitionObject Then Continue For
	If TypeOf oOcc.Definition Is VirtualComponentDefinition Then Continue For
	If oOcc.IsSubstituteOccurrence Then Continue For
	If oOcc.Suppressed Then Continue For
			
	If oOcc.Definition.SurfaceBodies.Count = 0 Then
		MessageBox.Show(oOcc.ReferencedDocumentDescriptor.FullDocumentName.ToString & System.Environment.NewLine & "This document has no surface bodies, it will be deleted",strAppName)
		oOcc.Delete
		
	End If
Next
