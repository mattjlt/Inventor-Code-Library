Imports System.Windows.Forms
AddReference "System.Drawing.dll"
Imports System.Drawing
Imports Inventor
' Title: Place Detail Items
' Description: Get all listed items from BOM for view placement
' Version: 0.0a

' Notes:
' - 

Public Class RunMyForm
	Private Sub Main
		
		Dim strAppName As String = "Place Part Views"
		
		' Check a document is open
		If ThisApplication.Documents.Count = 0 Then
			MessageBox.Show("No Documents Are Open",strAppName)
			Exit Sub
		End If
			
		' Check document type
		If ThisApplication.ActiveDocument.DocumentType <> Inventor.DocumentTypeEnum.kDrawingDocumentObject Then
			MessageBox.Show("A drawing document must be open",strAppName)
			Exit Sub
		End If
		
		' Get current document
		Dim oDoc As Inventor.DrawingDocument = ThisApplication.ActiveDocument
		Dim oPL As Inventor.PartsList = Nothing
		
		' Create parts list found flag
		Dim bPartsListFound As Boolean = False
		
		' Get first part list
		For Each oSheet As Inventor.Sheet In oDoc.Sheets
			' Check there is a parts list
			If oSheet.PartsLists.Count = 0 Then Continue For
				' There is a parts list if up to here
				' Get parts list and exit iteration
				oPL = oSheet.PartsLists(1)
				bPartsListFound = True
			Exit For
		Next	

		' Check a parts list was found
		If bPartsListFound = False Then
			MessageBox.Show("No Parts List Found", strAppName)
			Exit Sub
		End If
		
		' Get all view filenames
		Dim lstViews As New List(Of String)
		lstViews = GetAllViewFilenames(oDoc)	
		
		' Convert Parts List Into Array
		Dim lstArray As New List(Of clsBOM)
		
		Dim oRow As Inventor.PartsListRow
		
		For Each oRow In oPL.PartsListRows
			Dim strFilename As String = oRow.ReferencedRows.Item(1).BOMRow.ComponentDefinitions.Item(1).Document.Fullfilename
			
			Dim newRow As New clsBOM()
			newRow._Detailed = lstViews.Contains(strFilename) ' Check if filename is present in list of base views
			newRow._Item = oRow.Item(1).Value.ToString ' Item Column
			newRow._Description = oRow.Item(3).Value.ToString ' Description
			newRow._Filename = System.IO.Path.GetFileName(strFilename)
			newRow._FullFilename = strFilename
			lstArray.Add(newRow)
		Next
		
		' Create new instance of the custom form (sends partslist to form)
        Dim myfrm As New CustomForm(lstArray,ThisApplication)
		Dim strPlaceFilename As String = ""
	
		' Display the custom form result - use ShowDialog so it waits for user / form close before continuing
		If (myfrm.ShowDialog() = DialogResult.OK) Then
			' Get filename from result (already checked it's a valid filename)
        	strPlaceFilename = myfrm.myResult
			
			' Post filename to internal clipboard to be read by place view command
			ThisApplication.CommandManager.PostPrivateEvent(PrivateEventTypeEnum.kFileNameEvent, strPlaceFilename)
			
			' Initiate view place command - Execute2(False) allows user to manually place view
			' Initiate view place command - Execute2(True) allows user to manually place view and wait for selection to complete
			'ThisApplication.CommandManager.ControlDefinitions.Item("DrawingBaseViewCmd").Execute2(True) 
			
			ThisApplication.CommandManager.ControlDefinitions.Item("DrawingBaseViewCmd").Execute
			
			Dim oDrawDoc As DrawingDocument = ThisApplication.ActiveDocument
			Dim oSheet As Sheet = oDrawDoc.ActiveSheet
			Dim oView As DrawingView = oSheet.DrawingViews.Item(oSheet.DrawingViews.Count)

			Do While oView.IsUpdateComplete = False
			     Call  ThisApplication.UserInterfaceManager.DoEvents
			Loop
			
			' Clear internal clipboard to prevent issues with a preloaded filename for other commands
			ThisApplication.CommandManager.ClearPrivateEvents
		
		Else
			' Do nothing if dialog was cancelled
			Exit Sub
    	End If
	

			
		
    End Sub
		
		Private Function GetAllViewFilenames(ByRef oDoc As DrawingDocument) As List(Of String)
			
			' Need to create a new list to return as result, can't directly return function like a normal string
			Dim tempList As New List(Of String)
			
			' Iterate through all sheets
			For Each oSheet As Inventor.Sheet In oDoc.Sheets
				' Iterate through all base views
				For Each oView As Inventor.DrawingView In oSheet.DrawingViews
					' Check view type is base type
					If oView.ViewType = Inventor.DrawingViewTypeEnum.kStandardDrawingViewType Then
						' Add view filename to list
						tempList.Add(oView.ReferencedDocumentDescriptor.FullDocumentName)
					End If
				Next
			Next
			
			Return tempList
			
		End Function
		
End Class



Public Class CustomForm
	Inherits System.Windows.Forms.Form
	
	Public myResult As String = "Not Set"
	
	' Class global inventor access
	Public Shared ThisApplication As Inventor.Application
	
	'Get list + inventor application access from parent class (Can't access inventor from a new class otherwise)
	Public Sub New(ByRef lstArray As List(Of clsBOM), ByRef InvApp As Inventor.Application)
		
		' This is run when a new instance of the form is created		
		oForm = Me
		
		' Set global inventor application access from parent class
		ThisApplication = InvApp
		
		With oForm
			' Set up form	
			.FormBorderStyle = FormBorderStyle.SizableToolWindow 'Fixed3D / FixedDialog / FixedSingle / FixedToolWindow / None / Sizable / SizableToolWindow
			'.MaximizeBox = False
			'.MinimizeBox = False
			.StartPosition = FormStartPosition.CenterScreen
			.Width = 650
			.Height = 400
			.TopMost = True
			.Text = "Place Views"
			.Name = "Place Views"

		End With

		Dim Button1 As New Button()
		With Button1
			'.Font = myfnt
			.Text = "Place View"
			.Width = 100
			.Height = 30
			'.Top = 60
			'.Left = oForm.Width/2 - 100/2
			.Enabled = True
			.Dock = DockStyle.Bottom
		End With

		Dim oLV As New ListView
    		With oLV
		        .View = System.Windows.Forms.View.Details
		        .FullRowSelect = True
				.Columns.Add("Detailed",75,System.Windows.Forms.HorizontalAlignment.Center)
		        .Columns.Add("Item",50,System.Windows.Forms.HorizontalAlignment.Center)
		        .Columns.Add("Description",250,System.Windows.Forms.HorizontalAlignment.Left)
		        .Columns.Add("Filename", 200, System.Windows.Forms.HorizontalAlignment.Left)
				.Columns.Add("FullFilename",200,System.Windows.Forms.HorizontalAlignment.Left)
				
				.Dock = DockStyle.Fill
				' Name listview for button control direct access
				.Name = "ListView_Partslist"
   			End With

			
		'Add your Event handler
		AddHandler Button1.Click, AddressOf Button1_Click
'		AddHandler oLV.Click,AddressOf oLV_Click
		
		'Add controls to form
		oForm.Controls.Add(Button1)
		oForm.Controls.Add(oLV)
		oLV.BringToFront
		
		Dim oRefBOM As clsBOM
		
		' Load BOM list into ListView
		For Each oRefBOM In lstArray
			oLV.Items.Add(New ListViewItem({If(oRefBOM._Detailed,"True","False"),oRefBOM._Item,oRefBOM._Description,oRefBOM._Filename,oRefBOM._FullFilename}))
		Next
		
		' Set default dialog result
		Me.DialogResult = System.Windows.Forms.DialogResult.None
		
	End Sub

	Private Sub CustomForm_FormClosing(ByVal sender As Object, ByVal e As System.Windows.Forms.FormClosingEventArgs) Handles Me.FormClosing
	' Only run if dialog cance "x" button is clicked
	If Me.DialogResult = DialogResult.Cancel Then
	    If MessageBox.Show("Are you sure to close this application?", "Close", MessageBoxButtons.YesNo, MessageBoxIcon.Question) = System.Windows.Forms.DialogResult.Yes Then
		
	    Else
	      e.Cancel = True
	    End If
	End If
	 End Sub
  
	Private Sub Button1_Click(ByVal sender As System.Object, ByVal E As System.EventArgs)
	
		' Access form list view
		Dim tempLV As ListView = TryCast(Me.Controls("ListView_Partslist"), ListView)
		
		' Check selection was made, if not, exit out
		If tempLV.SelectedItems.Count = 0 Then
			MessageBox.Show("An item needs to be selected", "Selection Error")
			Exit Sub
		End If

		' Get selected item text
		Dim strFilename As String = tempLV.SelectedItems.Item(0).SubItems(4).Text
		
		' Verify filename is valid
		If Not System.IO.File.Exists(strFilename) Then
			' Filename is invalid
			MessageBox.Show("Filename :" & strFilename & ControlChars.NewLine & "Does Not Exist", "Selection Error")
			Exit Sub
		End If
		
		' Set result property string to filename
		myResult = strFilename
		
		' Set form result
		'Me.DialogResult = System.Windows.Forms.DialogResult.OK
		sender.parent.DialogResult = System.Windows.Forms.DialogResult.OK
		
		' Clost Form
		sender.Parent.Close		
	End Sub
	
'	Private Sub oLV_Click(ByVal sender As System.Object, ByVal E As System.EventArgs)
''		' Define sender as a listview object
''		Dim tempLV As ListView = TryCast(sender,ListView)
''		MessageBox.Show(tempLV.SelectedItems.Item(0).SubItems(1).Text)
''		MessageBox.Show("button clicked")
'''		Dim oLV As ListView.
'''		Me.DialogResult = System.Windows.Forms.DialogResult.OK
'''		Me.Close		
'	End Sub
	
	


End Class

Public Class clsBOM
	Public Property _Detailed As Boolean
    Public Property _Item As String
    Public Property _Description As String
    Public Property _Filename As String
	Public Property _FullFilename As String

	Public Sub New
			' This allows the creation of the class without having to prefill all the fields
	End Sub

    Public Sub New(ByVal bDetailed As Boolean,
					ByVal strItem As String,
					ByVal strDescription As String,
					ByVal strFilename As String,
					ByVal strFullFilename As Boolean)
		_Detailed = bDetailed
        _Item = strItem
        _Description = strDescription
        _Filename = strFilename
		_Filename = strFullFilename
        
	End Sub
	
End Class
